CDR DEFINITIONS ::= BEGIN

IMSI ::= NumericString (SIZE(15))
MSISDN ::= NumericString (SIZE(15))
TimeStamp ::= VisibleString (SIZE(19)) 
DataVolumeOctets ::= INTEGER (0..MAX)

CDRRecord ::= SEQUENCE {
    imsi IMSI,
    msisdn MSISDN,
    startTime TimeStamp,
    endTime TimeStamp,
	dataVolume     DataVolumeOctets,
    uplinkVolume DataVolumeOctets,
    downlinkVolume DataVolumeOctets
}
CDRRecords ::= SEQUENCE OF CDRRecord
END
